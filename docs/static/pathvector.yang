// This file is automatically generated by `pathvector yang`. Do not edit.
module pathvector {
  yang-version 1.1;
  namespace "urn:pathvector:config";
  prefix pv;

  organization "Pathvector";
  contact "https://github.com/natesales/pathvector";
  description
    "Configuration model of Pathvector, a declarative edge routing platform. This module is generated from the Pathvector configuration structs. Map sections of the YAML configuration (such as peers and templates) are modeled as lists keyed by name, and other maps are modeled as lists of key/value entries.";

  grouping bfd-instance {
    description "BFDInstance configuration";
    leaf neighbor {
      type string;
      description "Neighbor IP address";
    }
    leaf interface {
      type string;
      description "Interface (pattern accepted)";
    }
    leaf interval {
      type uint64;
      default "200";
      description "RX and TX interval";
    }
    leaf multiplier {
      type uint64;
      default "10";
      description "Number of missed packets for the state to be declared down";
    }
  }

  grouping mrt-instance {
    description "MRTInstance configuration";
    leaf file {
      type string;
      default "/var/log/bird/%N_%F_%T.mrt";
      description "File to store MRT dumps (supports strftime replacements and %N as table name)";
    }
    leaf interval {
      type uint64;
      default "300";
      description "Number of seconds between dumps";
    }
    leaf table {
      type string;
      description "Routing table to read from";
    }
  }

  grouping peer {
    description "Peer configuration";
    leaf template {
      type string;
      description "Configuration template (templates may also set a parent template)";
    }
    leaf merge-template-lists {
      type boolean;
      description "Merge list and map options configured on both this peer and its template instead of replacing the template's value (lists are appended to the template's, map entries override the template's)";
    }
    leaf description {
      type string;
      description "Peer description";
    }
    leaf-list comments {
      type string;
      ordered-by user;
      description "Comments in the generated peer configuration file";
    }
    leaf-list tags {
      type string;
      ordered-by user;
      description "Peer tags";
    }
    leaf disabled {
      type boolean;
      default "false";
      description "Should the sessions be disabled?";
    }
    leaf import {
      type boolean;
      default "true";
      description "Import routes from this peer";
    }
    leaf export {
      type boolean;
      default "true";
      description "Export routes to this peer";
    }
    leaf asn {
      type int64;
      default "0";
      description "Local ASN";
    }
    leaf-list neighbors {
      type string;
      ordered-by user;
      description "List of neighbor IPs";
    }
    leaf prepends {
      type int64;
      default "0";
      description "Number of times to prepend local AS on export";
    }
    leaf-list prepend-path {
      type uint32;
      ordered-by user;
      description "List of ASNs to prepend";
    }
    leaf clear-path {
      type boolean;
      default "false";
      description "Remove all ASNs from path (before prepends and prepend-path)";
    }
    leaf local-pref {
      type int64;
      default "100";
      description "BGP local preference";
    }
    leaf local-pref4 {
      type int64;
      description "IPv4 BGP local preference (overrides local-pref, not included in optimizer)";
    }
    leaf local-pref6 {
      type int64;
      description "IPv6 BGP local preference (overrides local-pref, not included in optimizer)";
    }
    leaf set-local-pref {
      type boolean;
      default "true";
      description "Should an explicit local pref be set? (iBGP sessions without local-pref, local-pref4/6 or set-local-pref configured keep the local pref received from the neighbor)";
    }
    leaf multihop {
      type boolean;
      default "false";
      description "Should BGP multihop be enabled? (255 max hops)";
    }
    leaf interface {
      type string;
      description "Interface for link-local BGP sessions";
    }
    leaf listen4 {
      type string;
      description "IPv4 BGP listen address (local address the session is sourced from)";
    }
    leaf listen6 {
      type string;
      description "IPv6 BGP listen address (local address the session is sourced from)";
    }
    leaf source4 {
      type string;
      description "Source IPv4 address of routes from this peer installed in the kernel (overrides the global source4)";
    }
    leaf source6 {
      type string;
      description "Source IPv6 address of routes from this peer installed in the kernel (overrides the global source6)";
    }
    leaf local-asn {
      type int64;
      description "Local ASN as defined in the global ASN field";
    }
    leaf local-port {
      type int64;
      default "179";
      description "Local TCP port";
    }
    leaf neighbor-port {
      type int64;
      default "179";
      description "Neighbor TCP port";
    }
    leaf passive {
      type boolean;
      default "false";
      description "Should we listen passively?";
    }
    leaf direct {
      type boolean;
      default "false";
      description "Specify that the neighbor is directly connected";
    }
    leaf next-hop-self {
      type boolean;
      default "false";
      description "Should BGP next-hop-self be enabled?";
    }
    leaf next-hop-self-ebgp {
      type boolean;
      default "false";
      description "Should BGP next-hop-self for eBGP be enabled?";
    }
    leaf next-hop-self-ibgp {
      type boolean;
      default "false";
      description "Should BGP next-hop-self for iBGP be enabled?";
    }
    leaf extended-next-hop {
      type boolean;
      default "false";
      description "Should RFC 8950 extended next hop encoding be enabled?";
    }
    leaf bfd {
      type boolean;
      default "false";
      description "Should BFD be enabled?";
    }
    leaf password {
      type string;
      description "BGP MD5 password";
    }
    leaf rs-client {
      type boolean;
      default "false";
      description "Should this peer be a route server client?";
    }
    leaf rr-client {
      type boolean;
      default "false";
      description "Should this peer be a route reflector client?";
    }
    leaf remove-private-asns {
      type boolean;
      default "true";
      description "Should private ASNs be removed from path before exporting?";
    }
    leaf l3vpn {
      type boolean;
      default "false";
      description "Should VPNv4 and VPNv6 (MPLS L3VPN, RFC 4364) routes be exchanged with this peer? Routes are kept in the vpntab4 and vpntab6 tables, e.g. for a route reflector";
    }
    leaf mp-unicast-46 {
      type boolean;
      default "false";
      description "Should this peer be configured with multiprotocol IPv4 and IPv6 unicast?";
    }
    leaf allow-local-as {
      type boolean;
      default "false";
      description "Should routes originated by the local ASN be accepted?";
    }
    leaf add-path-tx {
      type boolean;
      default "false";
      description "Enable BGP additional paths on export?";
    }
    leaf add-path-rx {
      type boolean;
      default "false";
      description "Enable BGP additional paths on import?";
    }
    leaf gateway {
      type string;
      description "BGP gateway mode, 'direct' or 'recursive' (BIRD defaults to direct for directly connected eBGP neighbors and recursive otherwise)";
    }
    leaf cost {
      type int64;
      description "Distance (IGP metric) to the BGP next hop for sessions in direct gateway mode (mainly direct sessions), used in best path selection in place of the IGP metric";
    }
    leaf import-next-hop {
      type string;
      description "Rewrite the BGP next hop before importing routes learned from this peer";
    }
    leaf export-next-hop {
      type string;
      description "Rewrite the BGP next hop before announcing routes to this peer";
    }
    leaf confederation {
      type int64;
      description "BGP confederation (RFC 5065)";
    }
    leaf confederation-member {
      type boolean;
      default "false";
      description "Should this peer be a member of the local confederation?";
    }
    leaf ttl-security {
      type boolean;
      default "false";
      description "RFC 5082 Generalized TTL Security Mechanism";
    }
    leaf interpret-communities {
      type boolean;
      default "true";
      description "Should well-known BGP communities be interpreted by their intended action?";
    }
    leaf default-local-pref {
      type int64;
      description "Default value for local preference";
    }
    leaf bgp-med {
      type int64;
      default "0";
      description "Value of the Multiple Exit Discriminator to be used during route selection when the MED attribute is missing";
    }
    leaf advertise-hostname {
      type boolean;
      default "false";
      description "Advertise hostname capability";
    }
    leaf disable-after-error {
      type boolean;
      default "false";
      description "Disable peer after error";
    }
    leaf prefer-older-routes {
      type boolean;
      default "false";
      description "Prefer older routes instead of comparing router IDs (RFC 5004)";
    }
    leaf irr-accept-child-prefixes {
      type boolean;
      default "false";
      description "Accept prefixes up to /24 and /48 from covering parent IRR objects";
    }
    leaf-list add-on-import {
      type string;
      ordered-by user;
      description "List of communities to add to all imported routes";
    }
    leaf-list add-on-export {
      type string;
      ordered-by user;
      description "List of communities to add to all exported routes";
    }
    leaf-list announce {
      type string;
      ordered-by user;
      description "Announce all routes matching these communities to the peer";
    }
    leaf-list remove-communities {
      type string;
      ordered-by user;
      description "List of communities to remove before from routes announced by this peer";
    }
    leaf remove-all-communities {
      type int64;
      description "Remove all standard and large communities beginning with this value";
    }
    list as-prefs {
      key "key";
      description "Map of ASN to import local pref (not included in optimizer)";
      leaf key {
        type uint32;
        description "Map key";
      }
      leaf value {
        type uint32;
        description "Map value";
      }
    }
    list as-prefs4 {
      key "key";
      description "Map of ASN to import local pref for IPv4 routes (overrides as-prefs, not included in optimizer)";
      leaf key {
        type uint32;
        description "Map key";
      }
      leaf value {
        type uint32;
        description "Map value";
      }
    }
    list as-prefs6 {
      key "key";
      description "Map of ASN to import local pref for IPv6 routes (overrides as-prefs, not included in optimizer)";
      leaf key {
        type uint32;
        description "Map key";
      }
      leaf value {
        type uint32;
        description "Map value";
      }
    }
    list prefix-prefs {
      key "key";
      description "Map of prefix (BIRD prefix pattern, IPv4 and IPv6 may be mixed) to import local pref (not included in optimizer, takes precedence over as-prefs and community-prefs)";
      leaf key {
        type string;
        description "Map key";
      }
      leaf value {
        type uint32;
        description "Map value";
      }
    }
    list community-prefs {
      key "key";
      description "Map of community to import local pref (not included in optimizer, as-prefs take precedence)";
      leaf key {
        type string;
        description "Map key";
      }
      leaf value {
        type uint32;
        description "Map value";
      }
    }
    leaf as-set {
      type string;
      description "Peer's as-set for filtering";
    }
    leaf import-limit4 {
      type int64;
      default "1500000";
      description "Maximum number of IPv4 prefixes to import after filtering";
    }
    leaf import-limit6 {
      type int64;
      default "1000000";
      description "Maximum number of IPv6 prefixes to import after filtering";
    }
    leaf import-limit-violation {
      type string;
      default "disable";
      description "What action should be taken when the import limit is tripped?";
    }
    leaf receive-limit4 {
      type int64;
      description "Maximum number of IPv4 prefixes to accept (including filtered routes, requires keep-filtered)";
    }
    leaf receive-limit6 {
      type int64;
      description "Maximum number of IPv6 prefixes to accept (including filtered routes, requires keep-filtered)";
    }
    leaf receive-limit-violation {
      type string;
      default "disable";
      description "What action should be taken when the receive limit is tripped?";
    }
    leaf export-limit4 {
      type int64;
      description "Maximum number of IPv4 prefixes to export";
    }
    leaf export-limit6 {
      type int64;
      description "Maximum number of IPv6 prefixes to export";
    }
    leaf export-limit-violation {
      type string;
      default "disable";
      description "What action should be taken when the export limit is tripped?";
    }
    leaf enforce-first-as {
      type boolean;
      default "true";
      description "Should we only accept routes who's first AS is equal to the configured peer address?";
    }
    leaf enforce-peer-nexthop {
      type boolean;
      default "true";
      description "Should we only accept routes with a next hop equal to the configured neighbor address?";
    }
    leaf force-peer-nexthop {
      type boolean;
      default "false";
      description "Rewrite nexthop to peer address";
    }
    leaf allow-blackhole-community {
      type boolean;
      default "false";
      description "Should this peer be allowed to send routes with the blackhole community? (Blackholed /32 and /128 routes are exempt from filter-prefix-length)";
    }
    leaf blackhole-in {
      type boolean;
      default "false";
      description "Should imported routes be blackholed?";
    }
    leaf blackhole-out {
      type boolean;
      default "false";
      description "Should exported routes be blackholed?";
    }
    leaf filter-irr {
      type boolean;
      default "false";
      description "Should IRR filtering be applied?";
    }
    leaf filter-rpki {
      type boolean;
      default "true";
      description "Should RPKI invalids be rejected?";
    }
    leaf strict-rpki {
      type boolean;
      default "false";
      description "Should only RPKI valids be accepted?";
    }
    leaf filter-max-prefix {
      type boolean;
      default "true";
      description "Should max prefix filtering be applied?";
    }
    leaf filter-bogon-routes {
      type boolean;
      default "true";
      description "Should bogon prefixes be rejected?";
    }
    leaf filter-bogon-asns {
      type boolean;
      default "true";
      description "Should paths containing a bogon ASN be rejected?";
    }
    leaf filter-transit-asns {
      type boolean;
      default "false";
      description "Should paths containing transit-free ASNs be rejected? (Peerlock Lite)'";
    }
    leaf filter-prefix-length {
      type boolean;
      default "true";
      description "Should too large/small prefixes (IPv4 8 > len > 24 and IPv6 12 > len > 48) be rejected?";
    }
    leaf filter-never-via-route-servers {
      type boolean;
      default "false";
      description "Should routes containing an ASN reported in PeeringDB to never be reachable via route servers be filtered?";
    }
    leaf filter-as-set {
      type boolean;
      default "false";
      description "Reject routes that aren't originated by an ASN within this peer's AS set";
    }
    leaf filter-aspa {
      type boolean;
      default "false";
      description "Reject routes that aren't originated by an ASN within the authorized-providers map";
    }
    leaf filter-blocklist {
      type boolean;
      default "true";
      description "Reject ASNs, prefixes, and IPs in the global blocklist";
    }
    leaf-list transit-lock {
      type string;
      ordered-by user;
      description "Reject routes that aren't transited by an AS in this list";
    }
    leaf-list dont-announce {
      type string;
      ordered-by user;
      description "Don't announce these prefixes to the peer (IPv4 and IPv6 may be mixed)";
    }
    leaf-list only-announce {
      type string;
      ordered-by user;
      description "Only announce these prefixes to the peer (IPv4 and IPv6 may be mixed, an address family with no prefixes in the list will not be announced)";
    }
    list prefix-communities {
      key "key";
      description "Map of prefix to community list to add to the prefix";
      leaf key {
        type string;
        description "Map key";
      }
      leaf-list value {
        type string;
        ordered-by user;
        description "Map value";
      }
    }
    leaf auto-import-limits {
      type boolean;
      default "false";
      description "Get import limits automatically from PeeringDB?";
    }
    leaf auto-as-set {
      type boolean;
      default "false";
      description "Get as-set automatically from PeeringDB? If no as-set exists in PeeringDB, a warning will be shown and the peer ASN used instead.";
    }
    leaf auto-as-set-members {
      type boolean;
      default "false";
      description "Get AS set members automatically from the peer's IRR as-set? (independent from auto-as-set)";
    }
    leaf verify-irr-policy {
      type boolean;
      default "false";
      description "Check the peer's aut-num object in the IRR (irr-server whois) for import (from us ... accept) and export (to us ... announce) policy, with us listed directly or through an as-set, and disable the peer if it's missing. Checked for each address family the peer has neighbors in; as there's one disabled flag per peer, the whole peer is disabled if any of them lacks policy. If the IRR can't be queried, a warning is shown and the peer is left as configured.";
    }
    leaf honor-graceful-shutdown {
      type boolean;
      default "true";
      description "Should RFC8326 graceful shutdown be enabled?";
    }
    leaf-list prefixes {
      type string;
      ordered-by user;
      description "Prefixes to accept";
    }
    leaf-list as-set-members {
      type uint32;
      ordered-by user;
      description "AS set members (For filter-as-set)";
    }
    leaf role {
      type string;
      description "RFC 9234 Local BGP role";
    }
    leaf require-roles {
      type boolean;
      default "false";
      description "Require RFC 9234 BGP roles";
    }
    leaf announce-default {
      type boolean;
      default "false";
      description "Should a default route be exported to this peer?";
    }
    leaf announce-originated {
      type boolean;
      default "true";
      description "Should locally originated routes be announced to this peer?";
    }
    leaf announce-all {
      type boolean;
      default "false";
      description "Should all routes be exported to this peer?";
    }
    leaf session-global {
      type string;
      description "Configuration to add to each session before any defined BGP protocols";
    }
    leaf pre-import-filter {
      type string;
      description "Configuration to add before the filtering section of the import policy";
    }
    leaf post-import-filter {
      type string;
      description "Configuration to add after the filtering section of the import filter";
    }
    leaf pre-import-accept {
      type string;
      description "Configuration to add immediately before the final accept term import";
    }
    leaf pre-export {
      type string;
      description "Configuration to add before the export policy";
    }
    leaf pre-export-final {
      type string;
      description "Configuration to add after the export policy before the final accept/reject term";
    }
    leaf-list probe-sources {
      type string;
      ordered-by user;
      description "Optimizer probe source addresses";
    }
    leaf optimize-inbound {
      type boolean;
      default "false";
      description "Should the optimizer modify inbound policy?";
    }
  }

  grouping prefix-rule {
    description "PrefixRule configuration";
    leaf session {
      type string;
      description "Source session name (routes learned from it are matched)";
    }
    leaf prefix {
      type string;
      description "Prefix this rule applies to";
    }
    leaf action {
      type string;
      description "reject, blackhole, prepend, prepend1-3, no-transit, no-peers, no-export";
    }
    leaf-list targets {
      type string;
      ordered-by user;
      description "Template names this rule applies to (empty = default for the action)";
    }
    leaf asn {
      type uint32;
      description "ASN to prepend (defaults to the source session's ASN)";
    }
    leaf count {
      type int64;
      description "Number of times to prepend (action prepend, default 1)";
    }
  }

  grouping vrrp-instance {
    description "VRRPInstance configuration";
    leaf state {
      type string;
      description "VRRP instance state ('primary' or 'backup')";
    }
    leaf interface {
      type string;
      description "Interface to send VRRP packets on";
    }
    leaf vrid {
      type uint64;
      description "RFC3768 VRRP Virtual Router ID (1-255)";
    }
    leaf priority {
      type uint64;
      description "RFC3768 VRRP Priority";
    }
    leaf-list vips {
      type string;
      ordered-by user;
      description "List of virtual IPs";
    }
    leaf vip-interface {
      type string;
      description "Interface to bind virtual IPs to (defaults to the VRRP interface)";
    }
  }

  leaf-list include {
    type string;
    ordered-by user;
    description "List of glob patterns (relative to the config file directory) for additional config fragments to merge (peers, templates, vrrp, bfd, mrt)";
  }
  leaf api-listen {
    type string;
    description "Listen address for the management API (host:port or unix:///path). Empty disables the API";
  }
  leaf api-key {
    type string;
    description "Bearer token for API authentication";
  }
  leaf api-sessions-dir {
    type string;
    description "Directory for API-managed session fragments (default: sessions.d next to the config file)";
  }
  leaf report-url {
    type string;
    description "POST session state to this URL (e.g. XodoPanel /api/v1/bgp/report)";
  }
  leaf report-key {
    type string;
    description "API key sent as X-API-Key to report-url";
  }
  leaf report-interval {
    type int64;
    default "60";
    description "Seconds between state reports";
  }
  leaf report-router {
    type string;
    description "Router name included in state reports (default: hostname)";
  }
  leaf report-prefix-cap {
    type int64;
    default "1000";
    description "Maximum prefixes enumerated per session in state reports";
  }
  leaf peeringdb-query-timeout {
    type uint64;
    default "10";
    description "PeeringDB query timeout in seconds";
  }
  leaf peeringdb-api-key {
    type string;
    description "PeeringDB API key";
  }
  leaf peeringdb-cache {
    type boolean;
    default "true";
    description "Global option to cache PeeringDB network records in memory for the duration of a single run, so peers with the same ASN only query PeeringDB once (this does not disable PeeringDB queries; to stop querying PeeringDB for a peer, disable auto-import-limits and auto-as-set on that peer)";
  }
  leaf irr-query-timeout {
    type uint64;
    default "30";
    description "IRR query timeout in seconds";
  }
  leaf bird-directory {
    type string;
    default "/etc/bird/";
    description "Directory to store BIRD configs";
  }
  leaf bird-binary {
    type string;
    default "/usr/sbin/bird";
    description "Path to BIRD binary";
  }
  leaf bird-socket {
    type string;
    default "/run/bird/bird.ctl";
    description "UNIX control socket for BIRD";
  }
  leaf cache-directory {
    type string;
    default "/var/run/pathvector/cache/";
    description "Directory to store runtime configuration cache";
  }
  leaf keepalived-config {
    type string;
    default "/etc/keepalived.conf";
    description "Configuration file for keepalived";
  }
  leaf web-ui-file {
    type string;
    description "File to write web UI to (disabled if empty)";
  }
  leaf log-file {
    type string;
    default "syslog";
    description "Log file location";
  }
  leaf global-config {
    type string;
    description "Global BIRD configuration";
  }
  leaf device-scan-time {
    type int64;
    default "0";
    description "Time in seconds between interface scans of the BIRD device protocol (BIRD default if 0)";
  }
  leaf direct-check-link {
    type boolean;
    default "false";
    description "Should the BIRD direct protocol only import routes of interfaces with link up? (check link)";
  }
  leaf-list disable-protocols {
    type string;
    ordered-by user;
    description "Built-in BIRD protocols to leave out of the configuration so they can be defined in global-config or manual*.conf instead (device, direct, kernel4, kernel6)";
  }
  leaf peeringdb-url {
    type string;
    default "https://peeringdb.com/api/";
    description "PeeringDB API URL, can be set to a local PeeringDB cache server";
  }
  leaf-list blocklist {
    type string;
    ordered-by user;
    description "List of ASNs, prefixes, and IP addresses to block";
  }
  leaf-list blocklist-urls {
    type string;
    ordered-by user;
    description "List of URLs to fetch blocklists from";
  }
  leaf-list blocklist-files {
    type string;
    ordered-by user;
    description "List of files to fetch blocklists from";
  }
  list communities {
    key "key";
    description "Map of community names to standard or large communities, names can be used in place of communities in any community option";
    leaf key {
      type string;
      description "Map key";
    }
    leaf value {
      type string;
      description "Map value";
    }
  }
  leaf-list origin-communities {
    type string;
    ordered-by user;
    description "List of communities to accept as locally originated routes";
  }
  leaf-list local-communities {
    type string;
    ordered-by user;
    description "List of communities to add to locally originated prefixes";
  }
  leaf-list add-on-import {
    type string;
    ordered-by user;
    description "List of communities to add to all imported routes";
  }
  leaf-list add-on-export {
    type string;
    ordered-by user;
    description "List of communities to add to all exported routes";
  }
  leaf show-warning-message {
    type boolean;
    default "true";
    description "Show autogenerated warning banner on generated files";
  }
  leaf hostname {
    type string;
    description "Router hostname (default system hostname)";
  }
  leaf asn {
    type int64;
    default "0";
    description "Autonomous System Number";
  }
  leaf-list prefixes {
    type string;
    ordered-by user;
    description "List of prefixes to announce";
  }
  leaf router-id {
    type string;
    description "Router ID (dotted quad notation)";
  }
  leaf irr-server {
    type string;
    default "rr.ntt.net";
    description "Internet routing registry server";
  }
  leaf rtr-server {
    type string;
    default "rtr.rpki.cloudflare.com:8282";
    description "RPKI-to-router server";
  }
  leaf bgpq-args {
    type string;
    description "Additional command line arguments to pass to bgpq4";
  }
  leaf bird-timeout {
    type int64;
    default "60";
    description "Timeout in seconds for BIRD socket commands (dial capped at 10s)";
  }
  leaf skip-peeringdb {
    type boolean;
    default "false";
    description "Skip PeeringDB queries (auto-import-limits, auto-as-set, NVRS) - peers render with default limits and no auto as-set";
  }
  leaf skip-irr {
    type boolean;
    default "false";
    description "Skip bgpq4/IRR queries (filter-irr, auto-as-set-members) - IRR prefix-set filters are omitted";
  }
  leaf action-communities {
    type boolean;
    default "false";
    description "Render the action/informational community function library (prepend/no-announce/RPKI marking helpers) into the global config";
  }
  leaf pop-id {
    type int64;
    description "PoP/site ID used by the action community library (rendered as 'define pop_id = N'; alternatively define pop_id yourself via global-config)";
  }
  container community-ids {
    description "Community numbering used by the action community library (all values have defaults)";
    leaf no-announce-as {
      type int64;
      description "LC id for 'do not announce to AS X' (payload = peer ASN)";
    }
    leaf no-announce-ix {
      type int64;
      description "LC id for 'do not announce at IX X' (payload = IX id)";
    }
    leaf prepend-general {
      type int64;
      description "LC id for general prepending (payload = prepend count 1-3)";
    }
    leaf-list prepend-as {
      type int64;
      ordered-by user;
      description "LC ids for per-AS prepending, index 0/1/2 = prepend x1/x2/x3 (payload = peer ASN)";
    }
    leaf-list prepend-ix {
      type int64;
      ordered-by user;
      description "LC ids for per-IX prepending, index 0/1/2 = prepend x1/x2/x3 (payload = IX id)";
    }
    leaf info-source {
      type int64;
      description "Informational LC id marking origin/import source";
    }
    leaf info-ix {
      type int64;
      description "Informational LC id marking learned-at-IX";
    }
    leaf info-upstream {
      type int64;
      description "Informational LC id marking learned-via-upstream";
    }
    leaf info-rpki {
      type int64;
      description "Informational LC id marking RPKI state (payload 100/101/102 = valid/unknown/invalid)";
    }
    leaf downstream-tag {
      type int64;
      description "Tag value for downstream marking (standard + large communities)";
    }
    leaf upstream-tag {
      type int64;
      description "Tag value for upstream marking (standard + large communities)";
    }
  }
  list prefix-rules {
    ordered-by user;
    description "Per-prefix routing policies applied at export on matching sessions";
    uses prefix-rule;
  }
  leaf keep-filtered {
    type boolean;
    default "false";
    description "Should filtered routes be kept in memory?";
  }
  leaf merge-paths {
    type boolean;
    default "false";
    description "Should best and equivalent non-best routes be imported to build ECMP routes?";
  }
  leaf source4 {
    type string;
    description "Source IPv4 address of BGP routes installed in the kernel (krt_prefsrc), can be overridden per peer";
  }
  leaf source6 {
    type string;
    description "Source IPv6 address of BGP routes installed in the kernel (krt_prefsrc), can be overridden per peer";
  }
  leaf default-route {
    type boolean;
    default "true";
    description "Add a default route";
  }
  leaf accept-default {
    type boolean;
    default "false";
    description "Should default routes be accepted from peers? When false, default routes are rejected by filter-prefix-length. When true, learned default routes are preferred over the locally generated default route and installed in the kernel.";
  }
  leaf rpki-enable {
    type boolean;
    default "true";
    description "Enable RPKI protocol";
  }
  leaf-list transit-asns {
    type uint32;
    ordered-by user;
    description "List of ASNs to consider transit providers for filter-transit-asns (default list in config)";
  }
  leaf-list bogons4 {
    type string;
    ordered-by user;
    description "List of IPv4 bogons (default list in config)";
  }
  leaf-list bogons6 {
    type string;
    ordered-by user;
    description "List of IPv6 bogons (default list in config)";
  }
  leaf-list bogon-asns {
    type string;
    ordered-by user;
    description "List of ASNs to consider bogons (default list in config)";
  }
  leaf blackhole-bogon-asns {
    type boolean;
    default "false";
    description "Should routes containing bogon ASNs be blackholed?";
  }
  leaf no-announce {
    type boolean;
    default "false";
    description "Don't announce any routes to any peer";
  }
  leaf no-accept {
    type boolean;
    default "false";
    description "Don't accept any routes from any peer";
  }
  leaf stun {
    type boolean;
    default "false";
    description "Don't accept or announce any routes from any peer (sets no-announce and no-accept)";
  }
  list authorized-providers {
    key "key";
    description "Map of origin ASN to authorized provider ASN list";
    leaf key {
      type uint32;
      description "Map key";
    }
    leaf-list value {
      type uint32;
      ordered-by user;
      description "Map value";
    }
  }
  list peers {
    key "name";
    description "BGP peer configuration";
    leaf name {
      type string;
      description "Unique name of this entry";
    }
    uses peer;
  }
  list templates {
    key "name";
    description "BGP peer templates";
    leaf name {
      type string;
      description "Unique name of this entry";
    }
    uses peer;
  }
  list vrrp {
    key "name";
    description "List of VRRP instances";
    leaf name {
      type string;
      description "Unique name of this entry";
    }
    uses vrrp-instance;
  }
  list bfd {
    key "name";
    description "BFD instances";
    leaf name {
      type string;
      description "Unique name of this entry";
    }
    uses bfd-instance;
  }
  list mrt {
    key "name";
    description "MRT instances";
    leaf name {
      type string;
      description "Unique name of this entry";
    }
    uses mrt-instance;
  }
  container kernel {
    description "Kernel routing configuration options";
    leaf-list accept4 {
      type string;
      ordered-by user;
      description "List of BIRD protocols to import into the IPv4 table";
    }
    leaf-list accept6 {
      type string;
      ordered-by user;
      description "List of BIRD protocols to import into the IPv6 table";
    }
    leaf-list reject4 {
      type string;
      ordered-by user;
      description "List of BIRD protocols to not import into the IPv4 table";
    }
    leaf-list reject6 {
      type string;
      ordered-by user;
      description "List of BIRD protocols to not import into the IPv6 table";
    }
    list statics {
      key "key";
      description "List of static routes to include in BIRD (always exported to the kernel, BIRD protocols statics4 and statics6)";
      leaf key {
        type string;
        description "Map key";
      }
      leaf value {
        type string;
        description "Map value";
      }
    }
    leaf-list srd-communities {
      type string;
      ordered-by user;
      description "List of communities to filter routes exported to kernel (if list is not empty, all other prefixes will not be exported)";
    }
    leaf learn {
      type boolean;
      default "false";
      description "Should routes from the kernel be learned into BIRD?";
    }
    leaf export {
      type boolean;
      default "true";
      description "Export routes to kernel routing table";
    }
    leaf reject-connected {
      type boolean;
      default "false";
      description "Don't export connected routes (RTS_DEVICE) to kernel?'";
    }
    leaf table {
      type int64;
      description "Kernel table";
    }
    leaf-list tables {
      type int64;
      ordered-by user;
      description "Additional kernel tables to export routes to, with the same export policy as the main kernel table (BIRD protocols kernel4_table<N> and kernel6_table<N>)";
    }
    leaf scan-time {
      type int64;
      default "10";
      description "Time in seconds between scans of the kernel routing table";
    }
  }
  container optimizer {
    description "Route optimizer options";
    leaf-list targets {
      type string;
      ordered-by user;
      description "List of probe targets";
    }
    leaf latency-threshold {
      type uint64;
      default "100";
      description "Maximum allowable latency in milliseconds";
    }
    leaf packet-loss-threshold {
      type decimal64 {
        fraction-digits 4;
      }
      default "0.5";
      description "Maximum allowable packet loss (percent)";
    }
    leaf modifier {
      type uint64;
      default "20";
      description "Amount to lower local pref by for depreferred peers";
    }
    leaf probe-count {
      type int64;
      default "5";
      description "Number of pings to send in each run";
    }
    leaf probe-timeout {
      type int64;
      default "1";
      description "Number of seconds to wait before considering the ICMP message unanswered";
    }
    leaf probe-interval {
      type int64;
      default "120";
      description "Number of seconds wait between each optimizer run";
    }
    leaf cache-size {
      type int64;
      default "15";
      description "Number of probe results to store per peer";
    }
    leaf probe-udp {
      type boolean;
      default "false";
      description "Use UDP probe (else ICMP)";
    }
    leaf alert-script {
      type string;
      description "Script to call on optimizer event";
    }
    leaf exit-on-cache-full {
      type boolean;
      default "false";
      description "Exit optimizer on cache full";
    }
  }
  list plugins {
    key "key";
    description "Plugin-specific configuration";
    leaf key {
      type string;
      description "Map key";
    }
    leaf value {
      type string;
      description "Map value";
    }
  }
}
